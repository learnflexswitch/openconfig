module openconfig-if-aggregate {

  yang-version "1";

  // namespace
  namespace "http://openconfig.net/yang/interface/aggregate";

  prefix "lag";

  // import some basic types
  import openconfig-interfaces { prefix ocif; }
  import openconfig-if-ethernet { prefix eth; }
  import ietf-yang-types { prefix yang; }
  import iana-if-type { prefix ift; }
  import openconfig-extensions { prefix oc-ext; }

  // meta
  organization "OpenConfig working group";

  contact
    "OpenConfig working group
    netopenconfig@googlegroups.com";

  description
    "Model for managing aggregated interfaces, including LACP-
    managed aggregates";

  oc-ext:openconfig-version "0.1.1";

  revision "2015-10-09" {
    description
      "Initial OpenConfig public release";
    reference "0.1.1";
  }

  revision "2015-08-20" {
    description
      "Initial revision";
    reference "Pre-release";
  }

  // extension statements

  // feature statements

  // identity statements

  // typedef statements

  typedef lacp-activity-type {
    type enumeration {
      enum ACTIVE {
        description
          "Interface is an active member, i.e., will detect and
          maintain aggregates";
      }
      enum PASSIVE {
        description
          "Interface is a passive member, i.e., it participates
          with an active partner";
      }
    }
    description
      "Describes the LACP membership type, active or passive, of the
      interface in the aggregate";
    reference "IEEE 802.1AX-2008";
  }

  typedef lacp-timeout-type {
    type enumeration {
      enum LONG {
        description
          "Participant wishes to use long timeouts to detect
          status of the aggregate, i.e., will expect less frequent
          transmissions. Long timeout is 90 seconds.";
      }
      enum SHORT {
        description
          "Participant wishes to use short timeouts, i.e., expects
          frequent transmissions to aggressively detect status
          changes. Short timeout is 3 seconds.";
      }
    }
    description
      "Type of timeout used, short or long, by LACP participants";
    reference "IEEE 802.1AX-2008";
  }

  typedef lacp-synchronization-type {
    type enumeration {
      enum IN_SYNC {
        description
          "Participant is in sync with the system id and key
          transmitted";
      }
      enum OUT_SYNC {
        description
          "Participant is not in sync with the system id and key
          transmitted";
      }
    }
    description
      "Indicates LACP synchronization state of participant";
    reference "IEEE 802.1AX-2008";
  }

  typedef lacp-period-type {
    type enumeration {
      enum FAST {
        description "Send LACP packets every second";
      }
      enum SLOW {
        description "Send LACP packets every 30 seconds";
      }
    }
    description
      "Defines the period options for the time between sending
      LACP messages";
    reference "IEEE 802.3ad";
  }

  typedef aggregation-type {
    type enumeration {
      enum LACP {
        description "LAG managed by LACP";
      }
      enum STATIC {
        description "Statically configured bundle / LAG";
      }
    }
    description
      "Type to define the lag-type, i.e., how the LAG is
      defined and managed";
  }

  typedef aggregation-hash {
	type enumeration {
		enum LAYER2 {
			description "Uses XOR of hardware MAC addresses and packet type ID
		field to generate the hash. The formula is

		hash = source MAC XOR destination MAC XOR packet type ID
		slave number = hash modulo slave count

		This algorithm will place all traffic to a particular
		network peer on the same slave.

		This algorithm is 802.3ad compliant.";
		}
		enum LAYER2_3 {
			description "This policy uses a combination of layer2 and layer3
		protocol information to generate the hash.

		Uses XOR of hardware MAC addresses and IP addresses to
		generate the hash.  The formula is

		hash = source MAC XOR destination MAC XOR packet type ID
		hash = hash XOR source IP XOR destination IP
		hash = hash XOR (hash RSHIFT 16)
		hash = hash XOR (hash RSHIFT 8)
		And then hash is reduced modulo slave count.

		If the protocol is IPv6 then the source and destination
		addresses are first hashed using ipv6_addr_hash.

		This algorithm will place all traffic to a particular
		network peer on the same slave.  For non-IP traffic,
		the formula is the same as for the layer2 transmit
		hash policy.

		This policy is intended to provide a more balanced
		distribution of traffic than layer2 alone, especially
		in environments where a layer3 gateway device is
		required to reach most destinations.

		This algorithm is 802.3ad compliant.";
		}
		enum LAYER3_4 {
			description "This policy uses upper layer protocol information,
		when available, to generate the hash.  This allows for
		traffic to a particular network peer to span multiple
		slaves, although a single connection will not span
		multiple slaves.

		The formula for unfragmented TCP and UDP packets is

		hash = source port, destination port (as in the header)
		hash = hash XOR source IP XOR destination IP
		hash = hash XOR (hash RSHIFT 16)
		hash = hash XOR (hash RSHIFT 8)
		And then hash is reduced modulo slave count.

		If the protocol is IPv6 then the source and destination
		addresses are first hashed using ipv6_addr_hash.

		For fragmented TCP or UDP packets and all other IPv4 and
		IPv6 protocol traffic, the source and destination port
		information is omitted.  For non-IP traffic, the
		formula is the same as for the layer2 transmit hash
		policy.

		This algorithm is not fully 802.3ad compliant.  A
		single TCP or UDP conversation containing both
		fragmented and unfragmented packets will see packets
		striped across two interfaces.  This may result in out
		of order delivery.  Most traffic types will not meet
		this criteria, as TCP rarely fragments traffic, and
		most UDP traffic is not involved in extended
		conversations.  Other implementations of 802.3ad may
		or may not tolerate this noncompliance.";
		}
	}
  }

  typedef rx-machine-state {
	type enumeration {
		enum RX_CURRENT {
			description "LACP Rx Machine Current State";
		}
		enum RX_EXPIRED {
			description "LACP Rx Machine Expired State";
		}
  		enum RX_DEFAULTED {
			description "LACP Rx Machine Defaulted State";
		}
		enum RX_INITIALIZE {
			description "LACP Rx Machine Initialize State";
		}
		enum RX_LACP_DISABLED {
			description "LACP Rx Machine LACP Disabled State";
		}
		enum RX_PORT_DISABLE {
			description "LACP Rx Machine Port Disabled State";
		}		
	}
  }

  typedef mux-machine-state {
	type enumeration {
		enum MUX_DETACHED {
			description "LACP MUX Machine Detached State";
		}
		enum MUX_WAITING {
			description "LACP MUX Machine Waiting State";
		}
		enum MUX_ATTACHED {
			description "LACP MUX Machine Attached State";
		}
		enum MUX_COLLECTING {
			description "LACP MUX Machine Collecting State";
		}
		enum MUX_DISTRIBUTING {
			description "LACP MUX Machine Distributing State";
		}
		enum MUX_COLLECTING_DISTRIBUTING {
			description "LACP MUX Machine Collecting Distributing State";
		}
	}
  }

  typedef churn-machine-state {
	type enumeration {
		enum CHURN_NO_CHURN {
			description "LACP Churn Machine No Churn State";
		}
		enum CHURN_CHURN {
			description "LACP Churn Machine Churn State";
		}
	} 
  }


  // grouping statements

  grouping aggregation-lacp-config {
    description
      "Configuration data for LACP aggregate interfaces";

    leaf interval {
      type lacp-period-type;
      default SLOW;
      description
        "Set the period between LACP messages -- uses
        the lacp-period-type enumeration.";
    }

    leaf lacp-mode {
      type lacp-activity-type;
      default ACTIVE;
      description
        "ACTIVE is to initiate the transmission of LACP packets.
         PASSIVE is to wait for peer to initiate the transmission of
         LACP packets.";
        //TODO:some implementations configure the LACP mode on each
        //member interface rather than on the LAG interface.  There
        //may be use cases for this identified at a later time.
    }

    leaf system-id-mac {
      type yang:mac-address;
      description
        "The MAC address portion of the node's System ID. This is
        combined with the system priority to construct the 8-octet
        system-id";
    }

    leaf system-priority {
      type uint16;
      description
        "Sytem priority used by the node on this LAG interface.
        Lower value is higher priority for determining which node
        is the controlling system.";
    }
	
	leaf lag-hash {
		type aggregation-hash;
		default LAYER2;
		description
		   "The tx hashing algorithm used by the lag group";
	}
  }

  grouping aggregation-lacp-state {
    description
      "Operational data for LACP aggregate interfaces";

  }

  grouping aggregation-lacp-top {
    description
      "Top level configuration and state variable containers for
      LACP data";

    container lacp {
      presence
        "Presence of the container enables LACP protocol on
        the aggregate interface";

      description
        "Configuration for LACP protocol operation on the
        aggregate interface";
      // TODO: need to add more parameters and operational state
      // container

      container config {
        description
          "Configuration data for LACP";

        uses aggregation-lacp-config;
      }

      container state {

        config false;
        description
          "Operational state data for LACP";

        uses aggregation-lacp-config;
        uses aggregation-lacp-state;
      }

      uses aggregation-lacp-members-top;

    }
  }

  grouping aggregation-lacp-members-config {
    description
      "Configuration data for lacp member interfaces";

    //currently a placeholder -- the list of member interfaces
    //and their status is considered opstate only
  }

  grouping aggregation-lacp-members-state {
    description
      "Operational status data for the member interfaces";

    leaf interface {
      type ocif:interface-ref;
      description
        "Interface member of the LACP aggregate";
    }

    leaf activity {
      type lacp-activity-type;
      description "Indicates participant is active or passive";
    }

    leaf timeout {
      type lacp-timeout-type;
      description
        "The timeout type (short or long) used by the
        participant";
    }

    leaf synchronization {
      type lacp-synchronization-type;
      description
        "Indicates whether the participant is in-sync or
        out-of-sync";
    }

    leaf aggregatable {
      type boolean;
      description
        "A true value indicates that the participant will allow
        the link to be used as part of the aggregate. A false
        value indicates the link should be used as an individual
        link";
    }

    leaf collecting {
      type boolean;
      description
        "If true, the participant is collecting incoming frames
        on the link, otherwise false";
    }

    leaf distributing {
      type boolean;
      description
        "When true, the participant is distributing outgoing
        frames; when false, distribution is disabled";
    }

    leaf system-id {
      type yang:mac-address;
      description
        "MAC address that defines the local system ID for the
        aggregate interface";
    }

    leaf oper-key {
      type uint16;
      description
        "Current operational value of the key for the aggregate
        interface";
    }

    leaf partner-id {
      type yang:mac-address;
      description
        "MAC address representing the protocol partner's interface
        system ID";
    }

    leaf partner-key {
      type uint16;
      description
        "Operational value of the protocol partner's key";
    }

	// same as AggregationPort
	leaf debug-id {
		type uint32;
		description 
			"Debug Information Id";
	}
	
	leaf rx-machine {
		type rx-machine-state;
		description
			"Current Rx Machine State";
	}
	
	leaf rx-time {
		type uint32;
		description
			"Time at which the last LACPDU was received by a given port, 
			in terms of centiseconds since the system was last reset";
	}
	
	leaf mux-machine {
		type mux-machine-state;
		description
			"Current MUX Machine State";
	}
	
	leaf mux-reason {
		type string;
		description
			"Reason for the most recent MUX state change";
	} 
	
	leaf actor-churn-machine {
		type churn-machine-state;
		description
			"Actor Churn Detection Machine State";
	}
	
	leaf partner-churn-machine {
		type churn-machine-state;
		description
			"Partner Churn Detection Machine State";
	}
	
	leaf actor-churn-count {
		type yang:counter64;
		description
			"Number of times the Actor State machine has entered the 
			ACTOR_CHURN state";
	}
	
	leaf partner-churn-count {
		type yang:counter64;
		description
			"Number of times the Partner State machine has entered the 
			ACTOR_CHURN state";
	}
	
	leaf actor-sync-transition-count {
		type yang:counter64;
		description
			"Number of times the Actor's Mux state machine has entered the 
			IN_SYNC state.";
	} 
	
	leaf partner-sync-transition-count {
		type yang:counter64;
		description
			"Number of times the Partner's Mux state machine has entered the 
			IN_SYNC state.";
	} 
	
	leaf actor-change-count {
		type yang:counter64;
		description
			"Number of times the Actor's perception of the LAG ID for the 
			Aggregation Port has changed.";
	}
	
	leaf partner-change-count {
		type yang:counter64;
		description
			"Number of times the Partner's perception of the LAG ID for the 
			Aggregation Port has changed.";
	}
	
	leaf actor-cds-churn-machine {
		type churn-machine-state;
		description
			"If supported Actor CDS Churn Machine State";
	}
	
	leaf partner-cds-churn-machine {
		type churn-machine-state;
		description
			"If supported Partner CDS Churn Machine State";
	}
	
	leaf actor-cds-churn-count {
		type yang:counter64;
		description
			"If supported the number of times the Actor CDS Churn state
			has entered the ACTOR_CDS_CHURN state";
	}
	
	leaf partner-cds-churn-count {
		type yang:counter64;
		description
			"If supported the number of times the Actor CDS Churn state
			has entered the ACTOR_CDS_CHURN state";
	}
    // TODO: rjs: unclear whether this is required, it is referenced
    //            elsewhere under the state container. The grouping
    //            does not exist.
    // added the new group below to provide LACP statistics.
    // uses aggregation-lacp-statistic;
  }

grouping aggregation-lacp-members-statistics {
    description
      "LACP packet statistics for the member interfaces";

    container counters {
      description
        "LACP protocol counters";

      leaf lacp-in-pkts {
        type yang:counter64;
        description
          "Number of LACPDUs received";
      }

      leaf lacp-out-pkts {
        type yang:counter64;
        description
          "Number of LACPDUs transmitted";
      }

      leaf lacp-rx-errors {
        type yang:counter64;
        description
          "Number of LACPDU receive packet errors";
      }

      leaf lacp-tx-errors {
        type yang:counter64;
        description
          "Number of LACPDU transmit packet errors";
      }

      leaf lacp-unknown-errors {
        type yang:counter64;
        description
          "Number of LACPDU unknown packet errors";
      }

      leaf lacp-errors {
        type yang:counter64;
        description
          "Number of LACPDU illegal packet errors";
      }
		
	  leaf lamp-in-pdu {
		type yang:counter64;
		description
			"Number of LAMPDU received";	
	  }
	
	  leaf lamp-in-response-pdu {
		type yang:counter64;
		description
			"Number of LAMPDU Response received";
	  }
	
	  leaf lamp-out-pdu {
		type yang:counter64;
		description
			"Number of LAMPDU transmited";	
	  }
	
	  leaf lamp-out-response-pdu {
		type yang:counter64;
		description
			"Number of LAMPDU Response received";
	  }
    }
  }

  grouping aggregation-lacp-members-top {
    description
      "Top-level grouping for aggregate members list";

    container members {
      config false;
      description
        "Enclosing container for the list of members interfaces of
        the aggregate. This list is considered operational state
        only so is labeled config false and has no config container";

      list member {
        key  interface;
        description
          "List of member interfaces and their associated status for
          a LACP-controlled aggregate interface.  Member list is not
          configurable here -- each interface indicates items
          its participation in the LAG.";

        leaf interface {
          type leafref {
            path "../state/interface";
          }
          description
            "Reference to aggregate member interface";
        }


        container state {

          config false;

          description
            "Operational state data for aggregate members";

          uses aggregation-lacp-members-state;
          uses aggregation-lacp-members-statistics;
        }
      }
    }
  }


  grouping aggregation-logical-config {
    description
      "Configuration data for aggregate interfaces";


    leaf lag-type {
      type aggregation-type;
      description
        "Sets the type of LAG, i.e., how it is
        configured / maintained";
    }

    leaf min-links {
      type uint16;
      description
        "Specifies the mininum number of member
        interfaces that must be active for the aggregate interface
        to be available";
    }

  }

  grouping ethernet-if-aggregation-config {
    description
      "Adds configuration items for Ethernet interfaces
      belonging to a logical aggregate / LAG";

    leaf aggregate-id {
      type ocif:interface-ref;
      must "ocif:type = 'ift:ieee8023adLag'" {
        description "The referenced interface must be a
        LAG interface.";
      }
      description
        "Specify the logical aggregate interface to which
        this interface belongs";
    }
  }

  grouping aggregation-logical-top {
    description "Top-level data definitions for LAGs";

    container aggregation {

      presence "Sets the interface to be a logical aggregate / LAG";
      description
        "Options for logical interfaces representing
        aggregates";

      container config {
        description
          "Configuration variables for logical aggregate /
          LAG interfaces";

        uses aggregation-logical-config;
      }

      container state {

        config false;
        description
          "Operational state variables for logical
          aggregate / LAG interfaces";

        uses aggregation-logical-config;
        //TODO: identity other state variable as the LAG level

        leaf-list members {
          //TODO: this should be active only for non-LACP LAGs,
          //otherwise the LAG state has the list of members and
          // their status
          when "lag:lag-type = 'STATIC'" {
            description
              "The simple list of member interfaces is active
              when the aggregate is statically configured";
          }
          type ocif:interface-ref;
          description
            "List of current member interfaces for the aggregate,
            expressed as references to existing interfaces";
        }
      }

      uses aggregation-lacp-top;
    }
  }


  // data definition statements

  // augment statements

  augment "/ocif:interfaces/ocif:interface" {
    when "ocif:type = 'ift:ieee8023adLag'" {
      description "active when the interface is set to type LAG";
    }
    description "Adds LAG configuration to the interface module";

    uses aggregation-logical-top;
  }

  augment "/ocif:interfaces/ocif:interface/eth:ethernet/" +
    "eth:config" {
    when "ocif:type = 'ift:ethernetCsmacd'" {
      description "active when the interface is Ethernet";
    }
    description "Adds LAG settings to individual Ethernet
    interfaces";

    uses ethernet-if-aggregation-config;
  }

  augment "/ocif:interfaces/ocif:interface/eth:ethernet/" +
    "eth:state" {
    when "ocif:type = 'ift:ethernetCsmacd'" {
      description "active when the interface is Ethernet";
    }
    description "Adds LAG settings to individual Ethernet
    interfaces";

    uses ethernet-if-aggregation-config;
  }

  // rpc statements

  // notification statements

}
